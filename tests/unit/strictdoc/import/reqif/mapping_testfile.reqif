# Mapping_testfile

# Specification: Specification Document

## SR001 (functional)
The import function shall import a .reqif file and convert it to an .sdoc file.
- status: Draft
- allocation: Software
- asil: ASIL-A
- SpecRealtion Type -> HLR001

### HLR001 (functional)
The import function shall import a SpecObject from the .reqif file.
- status: Draft
- allocation: Software
- asil: ASIL-A

#### LLR001 (technical)
The mapping function shall map requirement_ID to UID.
- status: Draft
- allocation_to_component: Software
- asil: ASIL-A
- target_value: UID
- comment: no comment

##### LLR001-T001 (test)
- target_value: true
- objective: The test function shall test the mapping of the ReqIF attribute requirement_ID to the SDOC attribute UID.
- type: Software
- initial_condition: ReqIF requirement_ID is passed into the mapping function.
- test_sequence: The correct value for the requirement_ID shall be passed into the function and the function returns the same value as result and compares it to the predefined test value.
- status: Draft
- traceability: ..\..\..\tests\unit\strictdoc\import\reqif

##### LLR001-T002 (test)
- initial_condition: ReqIF requirement_ID is passed into the mapping function.
- status: Draft
- target_value: true
- type: Software
- test_sequence: The malformed requirement_ID shall be passed to the function and the function raises an ecxeption.
- objective: The test function shall test the mapping of the malformed ReqIF attribute requirement_ID to the SDoC attribute UID.
- traceability: ..\..\..\tests\unit\strictdoc\import\reqif

##### LLR001-T003 (test)
- target_value: true
- objective: The test function shall test the mapping of the missing ReqIF attribute requirement_ID to the SDoC attribute UID.
- type: Software
- initial_condition: ReqIF requirement_ID is passed into the mapping function.
- test_sequence: The empty value for the requirement_ID shall be passed to the function and the function raises an ecxeption.
- status: Draft
- traceability: ..\..\..\tests\unit\strictdoc\import\reqif

#### LLR002 (technical)
The mapping function shall map allocation to SPECIAL FIELD(allocation).
- status: Draft
- asil: ASIL-A
- allocation_to_component: Software
- target_value: SPECIAL FIELD(allocation)
- comment: no comment

##### LLR002-T001 (test)
- status: Draft
- target_value: true
- type: Software
- initial_condition: ReqIF allocation is passed into the mapping function.
- test_sequence: The correct value for the allocation shall be passed to the function and the function returns the same value as result and compares it to the predefined test value.
- objective: The test function shall test the mapping of the ReqIF attribute allocation to the SDoC attribute SPECIAL FIELD(allocation).
- traceability: ..\..\..\tests\unit\strictdoc\import\reqif

##### LLR002-T002 (test)
- status: Draft
- target_value: true
- type: Software
- initial_condition: ReqIF allocation is passed into the mapping function.
- test_sequence: The malformed allocation shall be passed to the function and the function raises an ecxeption.
- objective: The test function shall test the mapping of the malformed ReqIF attribute allocation to the SDoC attribute SPECIAL FIELD(allocation).
- traceability: ..\..\..\tests\unit\strictdoc\import\reqif

#### LLR003 (technical)
The mapping function shall map asil to SPECIAL FIELD(asil).
- status: Draft
- asil: ASIL-A
- allocation_to_component: Software
- target_value: SPECIAL FIELD(asil)
- comment: no comment

##### LLR003-T001 (test)
- status: Draft
- target_value: true
- type: Software
- initial_condition: ReqIF asil is passed into the mapping function.
- test_sequence: The correct value for the asil shall be passed to the function and the function returns the same value as result and compares it to the predefined test value.
- objective: The test function shall test the mapping of the ReqIF attribute asil to the SDoC attribute SPECIAL FIELD(asil).
- traceability: ..\..\..\tests\unit\strictdoc\import\reqif

##### LLR003-T002 (test)
- status: Draft
- target_value: true
- type: Software
- initial_condition: ReqIF asil is passed into the mapping function.
- test_sequence: The malformed asil shall be passed to the function and the function raises an ecxeption.
- objective: The test function shall test the mapping of the malformed ReqIF attribute asil to the SDoC attribute SPECIAL FIELD(asil).
- traceability: ..\..\..\tests\unit\strictdoc\import\reqif

#### LLR004 (technical)
The mapping function shall map status to STATUS.
- status: Draft
- asil: ASIL-A
- allocation_to_component: Software
- target_value: STATUS
- comment: no comment

##### LLR004-T001 (test)
- status: Draft
- target_value: true
- type: Software
- initial_condition: ReqIF status is passed into the mapping function.
- test_sequence: The correct value for the status shall be passed to the function and the function returns the same value as result and compares it to the predefined test value.
- objective: The test function shall test the mapping of the ReqIF attribute status to the SDoC attribute STATUS.
- traceability: ..\..\..\tests\unit\strictdoc\import\reqif

##### LLR004-T002 (test)
- status: Draft
- target_value: true
- type: Software
- initial_condition: ReqIF status is passed into the mapping function.
- test_sequence: The malformed status shall be passed to the function and the function raises an ecxeption.
- objective: The test function shall test the mapping of the malformed ReqIF attribute status to the SDoC attribute STATUS.
- traceability: ..\..\..\tests\unit\strictdoc\import\reqif

#### LLR005 (technical)
The mapping function shall map functional_description to TITLE.
- status: Draft
- asil: ASIL-A
- allocation_to_component: Software
- target_value: TITLE
- comment: no comment

##### LLR005-T001 (test)
- status: Draft
- target_value: true
- type: Software
- initial_condition: ReqIF functional_description is passed into the mapping function.
- test_sequence: The correct value for the functional_description shall be passed to the function and the function returns the same value as result and compares it to the predefined test value.
- objective: The test function shall test the mapping of the ReqIF attribute functional_description to the SDoC attribute TITLE.
- traceability: ..\..\..\tests\unit\strictdoc\import\reqif

##### LLR005-T002 (test)
- status: Draft
- target_value: true
- type: Software
- initial_condition: ReqIF functional_description is passed into the mapping function.
- test_sequence: The malformed functional_description shall be passed to the function and the function raises an ecxeption.
- objective: The test function shall test the mapping of the malformed ReqIF attribute functional_description to the SDoC attribute TITLE.
- traceability: ..\..\..\tests\unit\strictdoc\import\reqif

##### LLR005-T003 (test)
- status: Draft
- target_value: true
- type: Software
- initial_condition: ReqIF functional_description is passed into the mapping function.
- test_sequence: The empty value for the functional_description shall be passed to the function and the function raises an ecxeption.
- objective: The test function shall test the mapping of the missing ReqIF attribute functional_description to the SDoC attribute TITLE.
- traceability: ..\..\..\tests\unit\strictdoc\import\reqif

### HLR101 (functional)
The import function shall import a SpecObject from the .reqif file.
- status: Draft
- asil: ASIL-A
- allocation: Software

#### LLR101 (technical)
The mapping function shall map requirement_ID to UID.
- status: Draft
- asil: ASIL-A
- allocation_to_component: Software
- target_value: UID
- comment: no comment

##### LLR101-T001 (test)
- status: Draft
- target_value: true
- type: Software
- initial_condition: ReqIF requirement_ID is passed into the mapping function.
- test_sequence: The correct value for the requirement_ID shall be passed into the function and the function returns the same value as result and compares it to the predefined test value.
- objective: The test function shall test the mapping of the ReqIF attribute requirement_ID to the SDOC attribute UID.
- traceability: ..\..\..\tests\unit\strictdoc\import\reqif

##### LLR101-T002 (test)
- status: Draft
- target_value: true
- type: Software
- initial_condition: ReqIF requirement_ID is passed into the mapping function.
- test_sequence: The malformed requirement_ID shall be passed to the function and the function raises an ecxeption.
- objective: The test function shall test the mapping of the malformed ReqIF attribute requirement_ID to the SDoC attribute UID.
- traceability: ..\..\..\tests\unit\strictdoc\import\reqif

##### LLR101-T003 (test)
- status: Draft
- target_value: true
- type: Software
- initial_condition: ReqIF requirement_ID is passed into the mapping function.
- test_sequence: The empty value for the requirement_ID shall be passed to the function and the function raises an ecxeption.
- objective: The test function shall test the mapping of the missing ReqIF attribute requirement_ID to the SDoC attribute UID.
- traceability: ..\..\..\tests\unit\strictdoc\import\reqif

#### LLR102 (technical)
The mapping function shall map functional_description to TITLE.
- status: Draft
- asil: ASIL-A
- allocation_to_component: Software
- target_value: TITLE
- comment: no comment

##### LLR005-T001 (test)
- status: Draft
- target_value: true
- type: Software
- initial_condition: ReqIF functional_description is passed into the mapping function.
- test_sequence: The correct value for the functional_description shall be passed to the function and the function returns the same value as result and compares it to the predefined test value.
- objective: The test function shall test the mapping of the ReqIF attribute functional_description to the SDoC attribute TITLE.
- traceability: ..\..\..\tests\unit\strictdoc\import\reqif

##### LLR005-T002 (test)
- status: Draft
- target_value: true
- type: Software
- initial_condition: ReqIF functional_description is passed into the mapping function.
- test_sequence: The malformed functional_description shall be passed to the function and the function raises an ecxeption.
- objective: The test function shall test the mapping of the malformed ReqIF attribute functional_description to the SDoC attribute TITLE.
- traceability: ..\..\..\tests\unit\strictdoc\import\reqif

##### LLR005-T003 (test)
- status: Draft
- target_value: true
- type: Software
- initial_condition: ReqIF functional_description is passed into the mapping function.
- test_sequence: The empty value for the functional_description shall be passed to the function and the function raises an ecxeption.
- objective: The test function shall test the mapping of the missing ReqIF attribute functional_description to the SDoC attribute TITLE.
- traceability: ..\..\..\tests\unit\strictdoc\import\reqif

#### LLR103 (technical)
The mapping function shall map allocation_to_component to SPECIAL FIELD(allocation_to_component).
- status: Draft
- asil: ASIL-A
- allocation_to_component: Software
- target_value: SPECIAL FIELD(allocation_to_component)
- comment: no comment

##### LLR103-T001 (test)
- status: Draft
- target_value: true
- type: Software
- initial_condition: ReqIF allocation_to_component is passed into the mapping function.
- test_sequence: The correct value for the allocation_to_component shall be passed to the function and the function returns the same value as result and compares it to the predefined test value.
- objective: The test function shall test the mapping of the ReqIF attribute allocation_to_component to the SDoC attribute SPECIAL FIELD(allocation_to_component).
- traceability: ..\..\..\tests\unit\strictdoc\import\reqif

##### LLR103-T002 (test)
- status: Draft
- target_value: true
- type: Software
- initial_condition: ReqIF allocation_to_component is passed into the mapping function.
- test_sequence: The malformed allocation_to_component shall be passed to the function and the function raises an ecxeption.
- objective: The test function shall test the mapping of the malformed ReqIF attribute allocation_to_component to the SDoC attribute SPECIAL FIELD(allocation_to_component).
- traceability: ..\..\..\tests\unit\strictdoc\import\reqif

#### LLR104 (technical)
The mapping function shall map asil to SPECIAL FIELD(asil).
- status: Draft
- asil: ASIL-A
- allocation_to_component: Software
- target_value: SPECIAL FIELD(asil)
- comment: no comment

##### LLR104-T001 (test)
- status: Draft
- target_value: true
- type: Software
- initial_condition: ReqIF asil is passed into the mapping function.
- test_sequence: The correct value for the asil shall be passed to the function and the function returns the same value as result and compares it to the predefined test value.
- objective: The test function shall test the mapping of the ReqIF attribute asil to the SDoC attribute SPECIAL FIELD(asil).
- traceability: ..\..\..\tests\unit\strictdoc\import\reqif

##### LLR104-T002 (test)
- status: Draft
- target_value: true
- type: Software
- initial_condition: ReqIF asil is passed into the mapping function.
- test_sequence: The malformed asil shall be passed to the function and the function raises an ecxeption.
- objective: The test function shall test the mapping of the malformed ReqIF attribute asil to the SDoC attribute SPECIAL FIELD(asil).
- traceability: ..\..\..\tests\unit\strictdoc\import\reqif

#### LLR105 (technical)
The mapping function shall map status to STATUS.
- status: Draft
- asil: ASIL-A
- allocation_to_component: Software
- target_value: STATUS
- comment: no comment

##### LLR105-T001 (test)
- status: Draft
- target_value: true
- type: Software
- initial_condition: ReqIF status is passed into the mapping function.
- test_sequence: The correct value for the status shall be passed to the function and the function returns the same value as result and compares it to the predefined test value.
- objective: The test function shall test the mapping of the ReqIF attribute status to the SDoC attribute STATUS.
- traceability: ..\..\..\tests\unit\strictdoc\import\reqif

##### LLR105-T002 (test)
- status: Draft
- target_value: true
- type: Software
- initial_condition: ReqIF status is passed into the mapping function.
- test_sequence: The malformed status shall be passed to the function and the function raises an ecxeption.
- objective: The test function shall test the mapping of the malformed ReqIF attribute status to the SDoC attribute STATUS.
- traceability: ..\..\..\tests\unit\strictdoc\import\reqif

#### LLR106 (technical)
The mapping function shall map target_value to SPECIAL FIELD(target_value).
- status: Draft
- asil: ASIL-A
- allocation_to_component: Software
- target_value: SPECIAL FIELD(target_value)
- comment: no comment

##### LLR106-T001 (test)
- status: Draft
- target_value: true
- type: Software
- initial_condition: ReqIF target_value is passed into the mapping function.
- test_sequence: The correct value for the target_value shall be passed to the function and the function returns the same value as result and compares it to the predefined test value.
- objective: The test function shall test the mapping of the ReqIF attribute target_value to the SDoC attribute SPECIAL FIELD(target_value).
- traceability: ..\..\..\tests\unit\strictdoc\import\reqif

##### LLR106-T002 (test)
- status: Draft
- target_value: true
- type: Software
- initial_condition: ReqIF target_value is passed into the mapping function.
- test_sequence: The malformed target_value shall be passed to the function and the function raises an ecxeption.
- objective: The test function shall test the mapping of the malformed ReqIF attribute target_value to the SDoC attribute SPECIAL FIELD(target_value).
- traceability: ..\..\..\tests\unit\strictdoc\import\reqif

##### LLR106-T003 (test)
- status: Draft
- target_value: true
- type: Software
- initial_condition: ReqIF target_value is passed into the mapping function.
- test_sequence: The empty value for the target_value shall be passed to the function and the function raises an ecxeption.
- objective: The test function shall test the mapping of the missing ReqIF attribute target_value to the SDoC attribute SPECIAL FIELD(target_value).
- traceability: ..\..\..\tests\unit\strictdoc\import\reqif

#### LLR106 (technical)
The mapping function shall map comment to COMMENT.
- status: Draft
- asil: ASIL-A
- allocation_to_component: Software
- target_value: COMMENT
- comment: no comment

##### LLR106-T001 (test)
- status: Draft
- target_value: true
- type: Software
- initial_condition: ReqIF comment is passed into the mapping function.
- test_sequence: The correct value for the comment shall be passed to the function and the function returns the same value as result and compares it to the predefined test value.
- objective: The test function shall test the mapping of the ReqIF attribute comment to the SDoC attribute COMMENT.
- traceability: ..\..\..\tests\unit\strictdoc\import\reqif

##### LLR106-T002 (test)
- status: Draft
- target_value: true
- type: Software
- initial_condition: ReqIF comment is passed into the mapping function.
- test_sequence: The malformed comment shall be passed to the function and the function raises an ecxeption.
- objective: The test function shall test the mapping of the malformed ReqIF attribute comment to the SDoC attribute COMMENT.
- traceability: ..\..\..\tests\unit\strictdoc\import\reqif

### HLR201 (functional)
The import function shall import a SpecObject from the .reqif file.
- status: Draft
- asil: ASIL-A
- allocation: Software

#### LLR201 (technical)
The mapping function shall map requirement_ID to UID.
- status: Draft
- asil: ASIL-A
- allocation_to_component: Software
- target_value: UID
- comment: no comment

##### LLR201-T001 (test)
- status: Draft
- target_value: true
- type: Software
- initial_condition: ReqIF requirement_ID is passed into the mapping function.
- test_sequence: The correct value for the requirement_ID shall be passed to the function and the function returns the same value as result and compares it to the predefined test value.
- objective: The test function shall test the mapping of the ReqIF attribute requirement_ID to the SDoC attribute UID.
- traceability: ..\..\..\tests\unit\strictdoc\import\reqif

##### LLR201-T002 (test)
- status: Draft
- target_value: true
- type: Software
- initial_condition: ReqIF requirement_ID is passed into the mapping function.
- test_sequence: The malformed requirement_ID shall be passed to the function and the function raises an ecxeption.
- objective: The test function shall test the mapping of the malformed ReqIF attribute requirement_ID to the SDoC attribute UID.
- traceability: ..\..\..\tests\unit\strictdoc\import\reqif

##### LLR201-T003 (test)
- status: Draft
- target_value: true
- type: Software
- initial_condition: ReqIF requirement_ID is passed into the mapping function.
- test_sequence: The empty value for the requirement_ID shall be passed to the function and the function raises an ecxeption.
- objective: The test function shall test the mapping of the missing ReqIF attribute requirement_ID to the SDoC attribute UID.
- traceability: ..\..\..\tests\unit\strictdoc\import\reqif

#### LLR202 (technical)
The mapping function shall map traceability to REFS.
- status: Draft
- asil: ASIL-A
- allocation_to_component: Software
- target_value: REFS
- comment: no comment

##### LLR202-T001 (test)
- status: Draft
- target_value: true
- type: Software
- initial_condition: ReqIF traceability is passed into the mapping function.
- test_sequence: The correct value for the traceability shall be passed to the function and the function returns the same value as result and compares it to the predefined test value.
- objective: The test function shall test the mapping of the ReqIF attribute traceability to the SDoC attribute REFS.
- traceability: ..\..\..\tests\unit\strictdoc\import\reqif

##### LLR202-T002 (test)
- status: Draft
- target_value: true
- type: Software
- initial_condition: ReqIF traceability is passed into the mapping function.
- test_sequence: The malformed traceability shall be passed to the function and the function raises an ecxeption.
- objective: The test function shall test the mapping of the malformed ReqIF attribute traceability to the SDoC attribute REFS.
- traceability: ..\..\..\tests\unit\strictdoc\import\reqif

##### LLR202-T003 (test)
- status: Draft
- target_value: true
- type: Software
- initial_condition: ReqIF traceability is passed into the mapping function.
- test_sequence: The empty value for the traceability shall be passed to the function and the function raises an ecxeption.
- objective: The test function shall test the mapping of the missing ReqIF attribute traceability to the SDoC attribute REFS.
- traceability: ..\..\..\tests\unit\strictdoc\import\reqif

#### LLR203 (technical)
The mapping function shall map type to SPECIAL FIELD(type).
- status: Draft
- asil: ASIL-A
- allocation_to_component: Software
- target_value: SPECIAL FIELD(type)
- comment: no comment

##### LLR203-T001 (test)
- status: Draft
- target_value: true
- type: Software
- initial_condition: ReqIF type is passed into the mapping function.
- test_sequence: The correct value for the type shall be passed to the function and the function returns the same value as result and compares it to the predefined test value.
- objective: The test function shall test the mapping of the ReqIF attribute type to the SDoC attribute SPECIAL FIELD(type).
- traceability: ..\..\..\tests\unit\strictdoc\import\reqif

##### LLR203-T002 (test)
- status: Draft
- target_value: true
- type: Software
- initial_condition: ReqIF type is passed into the mapping function.
- test_sequence: The malformed type shall be passed to the function and the function raises an ecxeption.
- objective: The test function shall test the mapping of the malformed ReqIF attribute type to the SDoC attribute SPECIAL FIELD(type).
- traceability: ..\..\..\tests\unit\strictdoc\import\reqif

#### LLR204 (technical)
The mapping function shall map initial_condition to SPECIAL FIELD(initial_condition).
- status: Draft
- asil: ASIL-A
- allocation_to_component: Software
- target_value: SPECIAL FIELD(initial_condition)
- comment: no comment

##### LLR204-T001 (test)
- status: Draft
- target_value: true
- type: Software
- initial_condition: ReqIF initial_condition is passed into the mapping function.
- test_sequence: The correct value for the initial_condition shall be passed to the function and the function returns the same value as result and compares it to the predefined test value.
- objective: The test function shall test the mapping of the ReqIF attribute initial_condition to the SDoC attribute SPECIAL FIELD(initial_condition).
- traceability: ..\..\..\tests\unit\strictdoc\import\reqif

##### LLR204-T002 (test)
- status: Draft
- target_value: true
- type: Software
- initial_condition: ReqIF initial_condition is passed into the mapping function.
- test_sequence: The malformed initial_condition shall be passed to the function and the function raises an ecxeption.
- objective: The test function shall test the mapping of the malformed ReqIF attribute initial_condition to the SDoC attribute SPECIAL FIELD(initial_condition).
- traceability: ..\..\..\tests\unit\strictdoc\import\reqif

##### LLR204-T003 (test)
- status: Draft
- target_value: true
- type: Software
- initial_condition: ReqIF initial_condition is passed into the mapping function.
- test_sequence: The empty value for the initial_condition shall be passed to the function and the function raises an ecxeption.
- objective: The test function shall test the mapping of the missing ReqIF attribute initial_condition to the SDoC attribute SPECIAL FIELD(initial_condition).
- traceability: ..\..\..\tests\unit\strictdoc\import\reqif

#### LLR205 (technical)
The mapping function shall map status to STATUS.
- status: Draft
- asil: ASIL-A
- allocation_to_component: Software
- target_value: STATUS
- comment: no comment

##### LLR205-T001 (test)
- status: Draft
- target_value: true
- type: Software
- initial_condition: ReqIF status is passed into the mapping function.
- test_sequence: The correct value for the status shall be passed to the function and the function returns the same value as result and compares it to the predefined test value.
- objective: The test function shall test the mapping of the ReqIF attribute status to the SDoC attribute STATUS.
- traceability: ..\..\..\tests\unit\strictdoc\import\reqif

##### LLR205-T002 (test)
- status: Draft
- target_value: true
- type: Software
- initial_condition: ReqIF status is passed into the mapping function.
- test_sequence: The malformed status shall be passed to the function and the function raises an ecxeption.
- objective: The test function shall test the mapping of the malformed ReqIF attribute status to the SDoC attribute STATUS.
- traceability: ..\..\..\tests\unit\strictdoc\import\reqif

#### LLR206 (technical)
The mapping function shall map objective to TITLE.
- status: Draft
- asil: ASIL-A
- allocation_to_component: Software
- target_value: TITLE
- comment: no comment

##### LLR206-T001 (test)
- status: Draft
- target_value: true
- type: Software
- initial_condition: ReqIF objective is passed into the mapping function.
- test_sequence: The correct value for the objective shall be passed to the function and the function returns the same value as result and compares it to the predefined test value.
- objective: The test function shall test the mapping of the ReqIF attribute objective to the SDoC attribute TITLE.
- traceability: ..\..\..\tests\unit\strictdoc\import\reqif

##### LLR206-T002 (test)
- status: Draft
- target_value: true
- type: Software
- initial_condition: ReqIF objective is passed into the mapping function.
- test_sequence: The malformed objective shall be passed to the function and the function raises an ecxeption.
- objective: The test function shall test the mapping of the malformed ReqIF attribute technical_description to the SDoC attribute TITLE.
- traceability: ..\..\..\tests\unit\strictdoc\import\reqif

##### LLR206-T003 (test)
- status: Draft
- target_value: true
- type: Software
- initial_condition: ReqIF objective is passed into the mapping function.
- test_sequence: The empty value for the objective shall be passed to the function and the function raises an ecxeption.
- objective: The test function shall test the mapping of the missing ReqIF attribute technical_description to the SDoC attribute TITLE.
- traceability: ..\..\..\tests\unit\strictdoc\import\reqif

#### LLR207 (technical)
The mapping function shall map target_value to SPECIAL FIELD(target_value).
- status: Draft
- asil: ASIL-A
- allocation_to_component: Software
- target_value: SPECIAL FIELD(target_value)
- comment: no comment

##### LLR207-T001 (test)
- status: Draft
- target_value: true
- type: Software
- initial_condition: ReqIF target_value is passed into the mapping function.
- test_sequence: The correct value for the target_value shall be passed to the function and the function returns the same value as result and compares it to the predefined test value.
- objective: The test function shall test the mapping of the ReqIF attribute target_value to the SDoC attribute SPECIAL FIELD(target_value).
- traceability: ..\..\..\tests\unit\strictdoc\import\reqif

##### LLR207-T002 (test)
- status: Draft
- target_value: true
- type: Software
- initial_condition: ReqIF target_value is passed into the mapping function.
- test_sequence: The malformed target_value shall be passed to the function and the function raises an ecxeption.
- objective: The test function shall test the mapping of the malformed ReqIF attribute target_value to the SDoC attribute SPECIAL FIELD(target_value).
- traceability: ..\..\..\tests\unit\strictdoc\import\reqif

##### LLR207-T003 (test)
- status: Draft
- target_value: true
- type: Software
- initial_condition: ReqIF target_value is passed into the mapping function.
- test_sequence: The empty value for the target_value shall be passed to the function and the function raises an ecxeption.
- objective: The test function shall test the mapping of the missing ReqIF attribute target_value to the SDoC attribute SPECIAL FIELD(target_value).
- traceability: ..\..\..\tests\unit\strictdoc\import\reqif

#### LLR208 (technical)
The mapping function shall map test_sequence to SPECIAL FIELD(test_sequence).
- status: Draft
- asil: ASIL-A
- allocation_to_component: Software
- target_value: SPECIAL FIELD(test_sequence)
- comment: no comment

##### LLR208-T001 (test)
- status: Draft
- target_value: true
- type: Software
- initial_condition: ReqIF test_sequence is passed into the mapping function.
- test_sequence: The correct value for the test_sequence shall be passed to the function and the function returns the same value as result and compares it to the predefined test value.
- objective: The test function shall test the mapping of the ReqIF attribute test_sequence to the SDoC attribute SPECIAL FIELD(test_sequence).
- traceability: ..\..\..\tests\unit\strictdoc\import\reqif

##### LLR208-T002 (test)
- status: Draft
- target_value: true
- type: Software
- initial_condition: ReqIF test_sequence is passed into the mapping function.
- test_sequence: The malformed test_sequence shall be passed to the function and the function raises an ecxeption.
- objective: The test function shall test the mapping of the malformed ReqIF attribute test_sequence to the SDoC attribute SPECIAL FIELD(test_sequence).
- traceability: ..\..\..\tests\unit\strictdoc\import\reqif

##### LLR208-T003 (test)
- status: Draft
- target_value: true
- type: Software
- initial_condition: ReqIF test_sequence is passed into the mapping function.
- test_sequence: The empty value for the test_sequence shall be passed to the function and the function raises an ecxeption.
- objective: The test function shall test the mapping of the missing ReqIF attribute test_sequence to the SDoC attribute SPECIAL FIELD(test_sequence).
- traceability: ..\..\..\tests\unit\strictdoc\import\reqif
