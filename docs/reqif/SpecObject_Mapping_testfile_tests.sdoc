[DOCUMENT]
TITLE: SDoc Requirements
SPECIAL_FIELDS:
- NAME: ALLOCATION
  TYPE: String
- NAME: ASIL
  TYPE: String
- NAME: TARGET_VALUE
  TYPE: String
- NAME: ALLOCATION_TO_COMPONENT
  TYPE: String
- NAME: TYPE
  TYPE: String
- NAME: INITIAL_CONDITION
  TYPE: String
- NAME: TEST_SEQUENCE
  TYPE: String

[FREETEXT]
Defining the tests for mapping different tests from ReqIf files to SDOC
[/FREETEXT]

[SECTION]
TITLE: Mapping test requirements

[REQUIREMENT]
UID: HLR201
STATUS: Draft
SPECIAL_FIELDS:
  ALLOCATION: Software
  ASIL: none
REFS:
- TYPE: Parent
  VALUE: HLR010
STATEMENT: The SpecObjectParser shall map test requirements.

[REQUIREMENT]
UID: HLR201-T001
SPECIAL_FIELDS:
  TYPE: Software
  INITIAL_CONDITION: The etree element is passed into the SpecObjectParser function.
  TEST_SEQUENCE: The test requirement shall be passed into the function as an etree element and the function returns a Requirement Object which is compared to a predefined Requirement Object.
  TARGET_VALUE: The predefined Requirement Object.
REFS:
- TYPE: Parent
  VALUE: HLR201
- TYPE: File
  VALUE: ..\..\..\tests\unit\strictdoc\import\reqif
STATEMENT: The test function shall test the mapping of the etree element to a Requirement Object.

[REQUIREMENT]
UID: LLR201
STATUS: Draft
SPECIAL_FIELDS:
  ALLOCATION: Software
  ASIL: none
  TARGET_VALUE: UID
REFS:
- TYPE: Parent
  VALUE: HLR201
STATEMENT: The mapping function shall map requirement_ID to UID.
COMMENT: >>>
no comment
<<<

[REQUIREMENT]
UID: LLR201-T001
STATUS: Draft
SPECIAL_FIELDS:
  TYPE: Software
  INITIAL_CONDITION: ReqIF requirement_ID is passed into the mapping function.
  TEST_SEQUENCE: The correct value for the requirement_ID shall be passed to the function and the function returns the same value as result and compares it to the predefined test value.
  TARGET_VALUE: true
REFS:
- TYPE: Parent
  VALUE: LLR201
- TYPE: File
  VALUE: ..\..\..\tests\unit\strictdoc\import\reqif
STATEMENT: The test function shall test the mapping of the ReqIF attribute requirement_ID to the SDoC attribute UID.

[REQUIREMENT]
UID: LLR201-T002
STATUS: Draft
SPECIAL_FIELDS:
  TYPE: Software
  INITIAL_CONDITION: ReqIF requirement_ID is passed into the mapping function.
  TEST_SEQUENCE: The malformed requirement_ID shall be passed to the function and the function raises an ecxeption.
  TARGET_VALUE: true
REFS:
- TYPE: Parent
  VALUE: LLR201
- TYPE: File
  VALUE: ..\..\..\tests\unit\strictdoc\import\reqif
STATEMENT: The test function shall test the mapping of the malformed ReqIF attribute requirement_ID to the SDoC attribute UID.

[REQUIREMENT]
UID: LLR201-T003
STATUS: Draft
SPECIAL_FIELDS:
  TYPE: Software
  INITIAL_CONDITION: ReqIF requirement_ID is passed into the mapping function.
  TEST_SEQUENCE: The empty value for the requirement_ID shall be passed to the function and the function raises an ecxeption.
  TARGET_VALUE: true
REFS:
- TYPE: Parent
  VALUE: LLR201
- TYPE: File
  VALUE: ..\..\..\tests\unit\strictdoc\import\reqif
STATEMENT: The test function shall test the mapping of the missing ReqIF attribute requirement_ID to the SDoC attribute UID.

[REQUIREMENT]
UID: LLR202
STATUS: Draft
SPECIAL_FIELDS:
  ALLOCATION: Software
  ASIL: none
  TARGET_VALUE: REFS
REFS:
- TYPE: Parent
  VALUE: HLR201
STATEMENT: The mapping function shall map traceability to REFS.
COMMENT: >>>
no comment
<<<

[REQUIREMENT]
UID: LLR202-T001
STATUS: Draft
SPECIAL_FIELDS:
  TYPE: Software
  INITIAL_CONDITION: ReqIF traceability is passed into the mapping function.
  TEST_SEQUENCE: The correct value for the traceability shall be passed to the function and the function returns the same value as result and compares it to the predefined test value.
  TARGET_VALUE: true
REFS:
- TYPE: Parent
  VALUE: LLR202
- TYPE: File
  VALUE: ..\..\..\tests\unit\strictdoc\import\reqif
STATEMENT: The test function shall test the mapping of the ReqIF attribute traceability to the SDoC attribute REFS.

[REQUIREMENT]
UID: LLR202-T002
STATUS: Draft
SPECIAL_FIELDS:
  TYPE: Software
  INITIAL_CONDITION: ReqIF traceability is passed into the mapping function.
  TEST_SEQUENCE: The malformed traceability shall be passed to the function and the function raises an ecxeption.
  TARGET_VALUE: true
REFS:
- TYPE: Parent
  VALUE: LLR202
- TYPE: File
  VALUE: ..\..\..\tests\unit\strictdoc\import\reqif
STATEMENT: The test function shall test the mapping of the malformed ReqIF attribute traceability to the SDoC attribute REFS.

[REQUIREMENT]
UID: LLR202-T003
STATUS: Draft
SPECIAL_FIELDS:
  TYPE: Software
  INITIAL_CONDITION: ReqIF traceability is passed into the mapping function.
  TEST_SEQUENCE: The empty value for the traceability shall be passed to the function and the function raises an ecxeption.
  TARGET_VALUE: true
REFS:
- TYPE: Parent
  VALUE: LLR202
- TYPE: File
  VALUE: ..\..\..\tests\unit\strictdoc\import\reqif
STATEMENT: The test function shall test the mapping of the missing ReqIF attribute traceability to the SDoC attribute REFS.

[REQUIREMENT]
UID: LLR203
STATUS: Draft
SPECIAL_FIELDS:
  ALLOCATION: Software
  ASIL: none
  TARGET_VALUE: SPECIAL FIELD(type)
REFS:
- TYPE: Parent
  VALUE: HLR201
STATEMENT: The mapping function shall map type to SPECIAL FIELD(type).
COMMENT: >>>
no comment
<<<

[REQUIREMENT]
UID: LLR203-T001
STATUS: Draft
SPECIAL_FIELDS:
  TYPE: Software
  INITIAL_CONDITION: ReqIF type is passed into the mapping function.
  TEST_SEQUENCE: The correct value for the type shall be passed to the function and the function returns the same value as result and compares it to the predefined test value.
  TARGET_VALUE: true
REFS:
- TYPE: Parent
  VALUE: LLR203
- TYPE: File
  VALUE: ..\..\..\tests\unit\strictdoc\import\reqif
STATEMENT: The test function shall test the mapping of the ReqIF attribute type to the SDoC attribute SPECIAL FIELD(type).

[REQUIREMENT]
UID: LLR203-T002
STATUS: Draft
SPECIAL_FIELDS:
  TYPE: Software
  INITIAL_CONDITION: ReqIF type is passed into the mapping function.
  TEST_SEQUENCE: The malformed type shall be passed to the function and the function raises an ecxeption.
  TARGET_VALUE: true
REFS:
- TYPE: Parent
  VALUE: LLR203
- TYPE: File
  VALUE: ..\..\..\tests\unit\strictdoc\import\reqif
STATEMENT: The test function shall test the mapping of the malformed ReqIF attribute type to the SDoC attribute SPECIAL FIELD(type).

[REQUIREMENT]
UID: LLR204
STATUS: Draft
SPECIAL_FIELDS:
  ALLOCATION: Software
  ASIL: none
  TARGET_VALUE: SPECIAL FIELD(initial_condition)
REFS:
- TYPE: Parent
  VALUE: HLR201
STATEMENT: The mapping function shall map initial_condition to SPECIAL FIELD(initial_condition).
COMMENT: >>>
no comment
<<<

[REQUIREMENT]
UID: LLR204-T001
STATUS: Draft
SPECIAL_FIELDS:
  TYPE: Software
  INITIAL_CONDITION: ReqIF initial_condition is passed into the mapping function.
  TEST_SEQUENCE: The correct value for the initial_condition shall be passed to the function and the function returns the same value as result and compares it to the predefined test value.
  TARGET_VALUE: true
REFS:
- TYPE: Parent
  VALUE: LLR204
- TYPE: File
  VALUE: ..\..\..\tests\unit\strictdoc\import\reqif
STATEMENT: The test function shall test the mapping of the ReqIF attribute initial_condition to the SDoC attribute SPECIAL FIELD(initial_condition).

[REQUIREMENT]
UID: LLR204-T002
STATUS: Draft
SPECIAL_FIELDS:
  TYPE: Software
  INITIAL_CONDITION: ReqIF initial_condition is passed into the mapping function.
  TEST_SEQUENCE: The malformed initial_condition shall be passed to the function and the function raises an ecxeption.
  TARGET_VALUE: true
REFS:
- TYPE: Parent
  VALUE: LLR204
- TYPE: File
  VALUE: ..\..\..\tests\unit\strictdoc\import\reqif
STATEMENT: The test function shall test the mapping of the malformed ReqIF attribute initial_condition to the SDoC attribute SPECIAL FIELD(initial_condition).

[REQUIREMENT]
UID: LLR204-T003
STATUS: Draft
SPECIAL_FIELDS:
  TYPE: Software
  INITIAL_CONDITION: ReqIF initial_condition is passed into the mapping function.
  TEST_SEQUENCE: The empty value for the initial_condition shall be passed to the function and the function raises an ecxeption.
  TARGET_VALUE: true
REFS:
- TYPE: Parent
  VALUE: LLR402
- TYPE: File
  VALUE: ..\..\..\tests\unit\strictdoc\import\reqif
STATEMENT: The test function shall test the mapping of the missing ReqIF attribute initial_condition to the SDoC attribute SPECIAL FIELD(initial_condition).

[REQUIREMENT]
UID: LLR205
STATUS: Draft
SPECIAL_FIELDS:
  ALLOCATION: Software
  ASIL: none
  TARGET_VALUE: STATUS
REFS:
- TYPE: Parent
  VALUE: HLR201
STATEMENT: The mapping function shall map status to STATUS.

[REQUIREMENT]
UID: LLR205-T001
STATUS: Draft
SPECIAL_FIELDS:
  TYPE: Software
  INITIAL_CONDITION: ReqIF status is passed into the mapping function.
  TEST_SEQUENCE: The correct value for the status shall be passed to the function and the function returns the same value as result and compares it to the predefined test value.
  TARGET_VALUE: true
REFS:
- TYPE: Parent
  VALUE: LLR205
- TYPE: File
  VALUE: ..\..\..\tests\unit\strictdoc\import\reqif
STATEMENT: The test function shall test the mapping of the ReqIF attribute status to the SDoC attribute STATUS.

[REQUIREMENT]
UID: LLR205-T002
STATUS: Draft
SPECIAL_FIELDS:
  TYPE: Software
  INITIAL_CONDITION: ReqIF status is passed into the mapping function.
  TEST_SEQUENCE: The malformed status shall be passed to the function and the function raises an ecxeption.
  TARGET_VALUE: true
REFS:
- TYPE: Parent
  VALUE: LLR205
- TYPE: File
  VALUE: ..\..\..\tests\unit\strictdoc\import\reqif
STATEMENT: The test function shall test the mapping of the malformed ReqIF attribute status to the SDoC attribute STATUS.

[REQUIREMENT]
UID: LLR206
STATUS: Draft
SPECIAL_FIELDS:
  ALLOCATION: Software
  ASIL: none
  TARGET_VALUE: TITLE
REFS:
- TYPE: Parent
  VALUE: HLR201
STATEMENT: The mapping function shall map objective to TITLE.

[REQUIREMENT]
UID: LLR206-T101
STATUS: Draft
SPECIAL_FIELDS:
  TYPE: Software
  INITIAL_CONDITION: ReqIF objective is passed into the mapping function.
  TEST_SEQUENCE: The correct value for the objective shall be passed to the function and the function returns the same value as result and compares it to the predefined test value.
  TARGET_VALUE: true
REFS:
- TYPE: Parent
  VALUE: LLR206
- TYPE: File
  VALUE: ..\..\..\tests\unit\strictdoc\import\reqif
STATEMENT: The test function shall test the mapping of the ReqIF attribute objective to the SDoC attribute TITLE.

[REQUIREMENT]
UID: LLR206-T002
STATUS: Draft
SPECIAL_FIELDS:
  TYPE: Software
  INITIAL_CONDITION: ReqIF objective is passed into the mapping function.
  TEST_SEQUENCE: The malformed objective shall be passed to the function and the function raises an ecxeption.
  TARGET_VALUE: true
REFS:
- TYPE: Parent
  VALUE: LLR206
- TYPE: File
  VALUE: ..\..\..\tests\unit\strictdoc\import\reqif
STATEMENT: The test function shall test the mapping of the malformed ReqIF attribute objective to the SDoC attribute TITLE.

[REQUIREMENT]
UID: LLR206-T003
STATUS: Draft
SPECIAL_FIELDS:
  TYPE: Software
  INITIAL_CONDITION: ReqIF objective is passed into the mapping function.
  TEST_SEQUENCE: The empty value for the objective shall be passed to the function and the function raises an ecxeption.
  TARGET_VALUE: true
REFS:
- TYPE: Parent
  VALUE: LLR206
- TYPE: File
  VALUE: ..\..\..\tests\unit\strictdoc\import\reqif
STATEMENT: The test function shall test the mapping of the missing ReqIF attribute objective to the SDoC attribute TITLE.

[REQUIREMENT]
UID: LLR207
STATUS: Draft
SPECIAL_FIELDS:
  ALLOCATION: Software
  ASIL: none
  TARGET_VALUE: SPECIAL FIELD(target_value)
REFS:
- TYPE: Parent
  VALUE: HLR201
STATEMENT: The mapping function shall map target_value to SPECIAL FIELD(target_value).
COMMENT: >>>
no comment
<<<

[REQUIREMENT]
UID: LLR207-T001
STATUS: Draft
SPECIAL_FIELDS:
  TYPE: Software
  INITIAL_CONDITION: ReqIF target_value is passed into the mapping function.
  TEST_SEQUENCE: The correct value for the target_value shall be passed to the function and the function returns the same value as result and compares it to the predefined test value.
  TARGET_VALUE: true
REFS:
- TYPE: Parent
  VALUE: LLR207
- TYPE: File
  VALUE: ..\..\..\tests\unit\strictdoc\import\reqif
STATEMENT: The test function shall test the mapping of the ReqIF attribute target_value to the SDoC attribute SPECIAL FIELD(target_value).

[REQUIREMENT]
UID: LLR207-T002
STATUS: Draft
SPECIAL_FIELDS:
  TYPE: Software
  INITIAL_CONDITION: ReqIF target_value is passed into the mapping function.
  TEST_SEQUENCE: The malformed target_value shall be passed to the function and the function raises an ecxeption.
  TARGET_VALUE: true
REFS:
- TYPE: Parent
  VALUE: LLR207
- TYPE: File
  VALUE: ..\..\..\tests\unit\strictdoc\import\reqif
STATEMENT: The test function shall test the mapping of the malformed ReqIF attribute target_value to the SDoC attribute SPECIAL FIELD(target_value).

[REQUIREMENT]
UID: LLR207-T003
STATUS: Draft
SPECIAL_FIELDS:
  TYPE: Software
  INITIAL_CONDITION: ReqIF target_value is passed into the mapping function.
  TEST_SEQUENCE: The empty value for the target_value shall be passed to the function and the function raises an ecxeption.
  TARGET_VALUE: true
REFS:
- TYPE: Parent
  VALUE: LLR207
- TYPE: File
  VALUE: ..\..\..\tests\unit\strictdoc\import\reqif
STATEMENT: The test function shall test the mapping of the missing ReqIF attribute target_value to the SDoC attribute SPECIAL FIELD(target_value).

[REQUIREMENT]
UID: LLR208
STATUS: Draft
SPECIAL_FIELDS:
  ALLOCATION: Software
  ASIL: none
  TARGET_VALUE: SPECIAL FIELD(test_sequence)
REFS:
- TYPE: Parent
  VALUE: HLR201
STATEMENT: The mapping function shall map test_sequence to SPECIAL FIELD(test_sequence).
COMMENT: >>>
no comment
<<<

[REQUIREMENT]
UID: LLR208-T001
STATUS: Draft
SPECIAL_FIELDS:
  TYPE: Software
  INITIAL_CONDITION: ReqIF test_sequence is passed into the mapping function.
  TEST_SEQUENCE: The correct value for the test_sequence shall be passed to the function and the function returns the same value as result and compares it to the predefined test value.
  TARGET_VALUE: true
REFS:
- TYPE: Parent
  VALUE: LLR208
- TYPE: File
  VALUE: ..\..\..\tests\unit\strictdoc\import\reqif
STATEMENT: The test function shall test the mapping of the ReqIF attribute test_sequence to the SDoC attribute SPECIAL FIELD(test_sequence).

[REQUIREMENT]
UID: LLR208-T002
STATUS: Draft
SPECIAL_FIELDS:
  TYPE: Software
  INITIAL_CONDITION: ReqIF test_sequence is passed into the mapping function.
  TEST_SEQUENCE: The malformed test_sequence shall be passed to the function and the function raises an ecxeption.
  TARGET_VALUE: true
REFS:
- TYPE: Parent
  VALUE: LLR208
- TYPE: File
  VALUE: ..\..\..\tests\unit\strictdoc\import\reqif
STATEMENT: The test function shall test the mapping of the malformed ReqIF attribute test_sequence to the SDoC attribute SPECIAL FIELD(test_sequence).

[REQUIREMENT]
UID: LLR208-T003
STATUS: Draft
SPECIAL_FIELDS:
  TYPE: Software
  INITIAL_CONDITION: ReqIF test_sequence is passed into the mapping function.
  TEST_SEQUENCE: The empty value for the test_sequence shall be passed to the function and the function raises an ecxeption.
  TARGET_VALUE: true
REFS:
- TYPE: Parent
  VALUE: LLR208
- TYPE: File
  VALUE: ..\..\..\tests\unit\strictdoc\import\reqif
STATEMENT: The test function shall test the mapping of the missing ReqIF attribute test_sequence to the SDoC attribute SPECIAL FIELD(test_sequence).

[/SECTION]
